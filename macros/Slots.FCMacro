__title__ = "Create parallel slots in selected horizontal face"
__doc__ = "Select horizontal faces and run macro"
__url__ = "https://forum.freecad.org/viewtopic.php?t=107631"

import math

import FreeCAD
import FreeCADGui
import Part
from FreeCAD import Vector
from numpy import linspace

# default parameters which will be written to VarSet
parameters = {
    "Angle": (0, "Group 1 - Direction", "0 - slots along X, 90 - slots along Y"),

    "ConnectGap": (0, "Group 2", "Connect slot if gap less than this value"),
    "ExcludeShorter": (0, "Group 2",  "Skip slot with length shorter than this value"),

    "SlotDepth": (2, "Group 3 - Slot", "Slot depth"),
    "SlotWidth": (2, "Group 3 - Slot", "Slot width"),
    "SlotStep": (2, "Group 3 - Slot", "Minimal distance between slots"),
    "OffsetHoles": (1, "Group 3 - Slot", "Offset from bosses and holes"),

    "OffsetXLeft": (0, "Group 4 - Area", "Offset x for left side"),
    "OffsetXRight": (0, "Group 4 - Area", "Offset x for right side"),
    "OffsetYTop": (-1, "Group 4 - Area", "Offset y for top side (positive value increase area)"),
    "OffsetYBottom": (-1, "Group 4 - Area",  "Offset y for bottom side (positive value increase area)"),

    "ShowSlotCenterLine": (1, "Group 6", "1 - show center line, 0 - hide"),
    "Tolerance": (0.01, "Group 6", "Uses in cut shape operations"),
}

"""
                            top
                     p3--------------p2
       ^               |  --------  |
       |         left  |  --------  |  right
     y |               |  --------  |
       |             p0--------------p1
        ------>            bottom
          x
"""

def getExtFace(face):
    """getExtFace(face) ... return rectangular face extended along X and Y"""
    fbb = face.BoundBox

    p0 = fbb.getPoint(0)
    p0.x -= slot_width + offset_left_x
    p0.y -= offset_bottom_y
    p1 = fbb.getPoint(1)
    p1.x += slot_width + offset_right_x
    p1.y -= offset_bottom_y
    p2 = fbb.getPoint(2)
    p2.x += slot_width + offset_right_x
    p2.y += offset_top_y
    p3 = fbb.getPoint(3)
    p3.x -= slot_width + offset_left_x
    p3.y += offset_top_y

    e1 = Part.makeLine(p0, p1)
    e2 = Part.makeLine(p1, p2)
    e3 = Part.makeLine(p2, p3)
    e4 = Part.makeLine(p3, p0)

    ext_wire = Part.Wire([e1, e2, e3, e4])

    return Part.Face(ext_wire)


def getHoles(face):
    """getHoles(face) ... return inner faces with offset"""
    outer_wire = face.OuterWire
    outer_index = [w.hashCode() for w in face.Wires].index(outer_wire.hashCode())

    inner_wires = face.Wires
    del inner_wires[outer_index]

    holes = []
    for w in inner_wires:
        o1 = Part.Face(w.makeOffset2D(offset_holes))
        o2 = Part.Face(w.makeOffset2D(-offset_holes))
        holes.append(max((o1, o2), key=lambda o: o.Area))

    return holes


def makeSlot(edge):
    """makeSlot(edge) ... return slot (solid) from center edge or wire"""
    r = slot_width / 2  # arcs radius
    p1 = edge.Vertexes[0].Point
    p2 = edge.Vertexes[1].Point

    e1 = Part.makeLine(Vector(p1.x, p1.y - r, p1.z), Vector(p2.x, p2.y - r, p2.z))

    # right arc
    arc = Part.Arc(Vector(p2.x, p2.y - r, p2.z), Vector(p2.x + r, p2.y, p2.z), Vector(p2.x, p2.y + r, p2.z))
    e2 = Part.Edge(arc)

    e3 = Part.makeLine(Vector(p2.x, p2.y + r, p2.z), Vector(p1.x, p1.y + r, p1.z))

    # left arc
    arc = Part.Arc(Vector(p1.x, p1.y + r, p1.z), Vector(p1.x - r, p1.y, p1.z), Vector(p1.x, p1.y - r, p1.z))
    e4 = Part.Edge(arc)

    return Part.Face(Part.Wire([e1, e2, e3, e4])).extrude(Vector(0, 0, -slot_depth))


def processLine(line, holes):
    """processLine(line, holes) ... return wire without intersection with holes"""
    edges = Part.Wire(line).cut(holes, tolerance).Edges
    sedges = sorted(edges, key=lambda e: e.Vertexes[0].X)

    result = []
    for i in range(len(sedges) - 1):
        dist = sedges[i].distToShape(sedges[i + 1])[0]
        if dist <= connect_gap:
            sedges[i + 1] = combineEdges(sedges[i], sedges[i + 1])
        else:
            gaps.append(math.ceil(dist * 1000) / 1000)
            result.append(Part.Wire(sedges[i]))
    result.append(Part.Wire(sedges[-1]))

    return [w for w in result if w.Length >= exclude_shorter]


def combineEdges(edge1, edge2):
    """combineEdges(edge1, edge2) ... return edge created between farest points of edges"""
    points = [v.Point for e in (edge1, edge2) for v in e.Vertexes]
    points_sorted = sorted(points, key=lambda p: p.x)

    return Part.makeLine(points_sorted[0], points_sorted[-1])


print()
print("<<< Macro create parallel slots in selected horizontal face >>>")
print()

doc = FreeCAD.ActiveDocument
doc.openTransaction("Slots VarSet")  # allows to undo

# Seach VarSet which will keep parameters or create new
varset_name = "VarSet_Slot"
for obj in doc.Objects:
    if obj.Name == varset_name:
        varset = obj
        break
else:
    varset = doc.addObject('App::VarSet', varset_name)

for key, (value, group, tooltip) in parameters.items():
    if not hasattr(varset, key):
        varset.addProperty("App::PropertyFloat", key, group, tooltip)
        setattr(varset, key, value)

doc.commitTransaction()  # allows to undo


doc.openTransaction("Slots")  # allows to undo

# read parameters from varset
angle = varset.Angle
connect_gap = varset.ConnectGap
exclude_shorter = varset.ExcludeShorter
offset_holes = varset.OffsetHoles
slot_depth = varset.SlotDepth
slot_width = varset.SlotWidth
slot_step = varset.SlotStep
offset_left_x = varset.OffsetXLeft
offset_right_x = varset.OffsetXRight
offset_top_y = varset.OffsetYTop
offset_bottom_y = varset.OffsetYBottom
show_slot_center_line = varset.ShowSlotCenterLine
tolerance = varset.Tolerance

# process selected faces
for sel in FreeCADGui.Selection.getSelectionEx():
    obj = sel.Object
    shape = sel.Object.Shape.rotated(Vector(0,0,0), Vector(0,0,1), angle)
    face = sel.SubObjects[0].rotated(Vector(0,0,0), Vector(0,0,1), angle)  # selected face
    if not isinstance(face, Part.Face):
        continue

    # rectangular face extended along X
    ext_face = getExtFace(face)
    # Part.show(ext_face, "ext_face")

    # negative offset from inner wires to not intersects with holes
    holes = getHoles(face)
    # Part.show(Part.Compound(holes), "holes")

    # slots number
    y_length = ext_face.Edges[1].Length
    nr = math.ceil((y_length - slot_width)/ (slot_step + slot_width)) + 1

    start_x = ext_face.Vertexes[0].X
    end_x = ext_face.Vertexes[1].X
    start_y = ext_face.Vertexes[0].Y + slot_width / 2
    end_y = ext_face.Vertexes[3].Y - slot_width / 2
    positions = linspace(start_y, end_y, nr)  # positions slots along Y
    print("  Lines number:", len(positions))
    print("  Lines positions:", [round(float(y), 2) for y in positions])

    z = ext_face.BoundBox.ZMax

    # lines along face
    lines = [Part.makeLine(Vector(start_x, y, z), Vector(end_x, y, z)) for y in positions]
    # Part.show(Part.Compound(lines), "lines")

    gaps = []  # list of gaps
    cwires = [w for line in lines for w in processLine(line, holes)]
    if show_slot_center_line:
        cwires_comp = Part.Compound(cwires)
        cwires_comp.rotate(Vector(0, 0, 0), Vector(0, 0, 1), -angle)
        cwires_comp.translate(Vector(0, 0, -slot_depth))
        Part.show(cwires_comp, "cwires")

    print()
    print("  Minimal gaps:", sorted(gaps)[:10])
    print()
    print("  Minimal slots length:", sorted(round(w.Length, 2) for w in cwires)[:10])

    slots = [makeSlot(w) for w in cwires]
    # Part.show(Part.Compound(slots), "slots")

    cut_model = shape.cut(slots, tolerance)  # cut model by slots
    cut_model.rotate(Vector(0, 0, 0), Vector(0, 0, 1), -angle)  # return original rotation

    obj.ViewObject.Visibility = False

    obj_slot = Part.show(cut_model, f"{obj.Label}_Slots")

doc.commitTransaction()  # allows to undo
