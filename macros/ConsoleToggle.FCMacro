__title__ = "Toggle panels Python console and Report view"
__doc__ = "Selected objects sent to console and can be accessed by variables obj and objs"
__url__ = "https://forum.freecad.org/viewtopic.php?t=94589"

import FreeCADGui
from PySide import QtGui


mw=FreeCADGui.getMainWindow()

panelConsole = mw.findChild(QtGui.QDockWidget, 'Python console')
if not panelConsole:
    panelConsole = mw.findChild(QtGui.QDockWidget, 'Python Console')

panelReport = mw.findChild(QtGui.QDockWidget, 'Report view')
if not panelReport:
    panelReport = mw.findChild(QtGui.QDockWidget, 'Report View')

if panelReport.isVisible() or panelConsole.isVisible():
    panelReport.hide()
    panelConsole.hide()
else:
    panelReport.show()
    panelConsole.show()

print()
print("<<<<< Macro: Toggle panels Python console and Report view >>>>>")

selection = FreeCADGui.Selection.getSelectionEx()

if selection:
    subs = []
    print(f"    {len(selection)} objects (objs) sent to console:")
    for i, sel in enumerate(selection):
        obj = sel.Object
        subs.extend(sel.SubObjects)
        print(f"        objs[{i}]   {obj.Name}   {obj.TypeId}")
    print()
    print("    List of objects is available by variable:         objs")
    print("    Last selected object is available by variable:    obj")
    print("    List of sub shapes is available by variable:      subs")
    print("    Last selected sub shape is available by variable: sub")

    FreeCADGui.doCommand("selection = FreeCADGui.Selection.getSelectionEx()")
    FreeCADGui.doCommand("obj = shp = sub = None")
    FreeCADGui.doCommand("objs = []")
    FreeCADGui.doCommand("shps = []")
    FreeCADGui.doCommand("subs = []")
    FreeCADGui.doCommand("""for sel in selection:
    objs.append(sel.Object)
    if hasattr(sel.Object, "Shape"):
        shps.append(sel.Object.Shape)
    subs.extend(sel.SubObjects)""")
    FreeCADGui.doCommand("if objs: obj = objs[-1]")
    FreeCADGui.doCommand("if subs: sub = subs[-1]")
