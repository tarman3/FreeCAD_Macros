__title__ = "Approximate wires"
__doc__ = "Replace complicated shapes by simple arcs and lines"
__url__ = "https://forum.freecad.org/viewtopic.php?t=104519"

"""
1. Select objects in Tree view or 3d view
2. Run macro
"""


tolerance = 0.1


import FreeCAD
import FreeCADGui
import Part
import Path.Op.Util as OpUtil

def approximateWire(wire, tolerance=0.1):
    """approximateWire approximates any non-line/arc edges with lines or arcs.
    Edges that are lines or circular arcs are kept as-is.
    tolerance: Deflection tolerance for approximation. Must be positive if wire contains non-line/arc edges.
    Returns the wire with non-line/arc edges replaced by arcs and line segments.
    """
    if tolerance <= 0:
        tolerance = 0.1
        
    processed_edges = []
    modified = False
    for edge in wire.Edges:
        curve = edge.Curve
        if isinstance(curve, (Part.Line, Part.LineSegment, Part.Circle, Part.ArcOfCircle)):
            # Keep lines and arcs as-is
            processed_edges.append(edge)
        else:
            # Approximate with lines and arcs
            modified = True

            # Convert to BSpline first if appropriate, to enable arc fitting
            if isinstance(curve, (Part.Ellipse, Part.Hyperbola, Part.Parabola)):
                # Convert edge to NURBS (BSpline)
                shape = edge.toNurbs()
                edge = shape.Edges[0]
            elif isinstance(curve, Part.BezierCurve):
                # Convert BezierCurve to BSpline
                curve = edge.Curve.toBSpline()
                edge = curve.toShape()

            if isinstance(edge.Curve, Part.BSplineCurve):
                # Convert BSpline to arcs
                curve = edge.Curve
                trimmed_curve = curve.trim(*edge.ParameterRange)
                curves = trimmed_curve.toBiArcs(tolerance)
                for curve in curves:
                    processed_edges.append(curve.toShape())
            else:
                # For other curve types, fall back to discretization to line segments
                vertices = edge.discretize(Deflection=tolerance)
                line_edges = [
                    Part.makeLine(vertices[i], vertices[i + 1]) for i in range(len(vertices) - 1)
                ]
                processed_edges.extend(line_edges)

    # Reassemble the wire if any edges were replaced
    if modified:
        #return Part.Wire(processed_edges)
        return Part.Wire(Part.__sortEdges__(processed_edges))
    return wire

print()
print("--- Macro to approximate wires ---")
print(f"  tolerance = {tolerance}")

selection = FreeCADGui.Selection.getSelection()

doc = FreeCAD.ActiveDocument

for obj in selection:
    if not obj.isDerivedFrom("Part::Feature"):
        continue

    wires = obj.Shape.Wires
    if not wires:
        continue

    aWires = [approximateWire(w, tolerance=tolerance) for w in wires]
    if not aWires:
        continue

    newShape = Part.Compound(aWires)
        
    newName = obj.Name + "_approximate"
    newObj = doc.addObject("Part::Feature", newName)
    newObj.Shape = newShape
    
    print()
    print(f"  {obj.Label}")
    print(f"    Edges {len(obj.Shape.Edges)} -> {len(newObj.Shape.Edges)}")
