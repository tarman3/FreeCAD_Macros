__title__ = "Export raw gcode 3"
__doc__ = "Save to file raw gcode (with tabs) from selected operations"
__url__ = "https://forum.freecad.org/viewtopic.php?t=99970"

import FreeCAD
import FreeCADGui
import PathScripts.PathUtils as PathUtils
import os


tab = "    "


def save2file(string):
    doc = FreeCAD.activeDocument()
    doc_filename = doc.FileName
    dirname = os.path.dirname(doc_filename)
    basename = os.path.basename(doc_filename).partition('.')[0]
    filename = basename + '.nc'
    file_path = os.path.join(dirname, filename)

    with open(file_path, "w") as f:
        f.write(string)

    print()
    print(f"Export pseudo gcode to file: {file_path}")


selection = FreeCADGui.Selection.getSelection()

output = ""
for obj in selection:
    if obj.isDerivedFrom("Path::Feature") and obj.Path.Commands:
        path = PathUtils.getPathWithPlacement(obj)
        for i, cmd in enumerate(path.Commands):
            if i == 0:
                output += cmd.toGCode() + "\n"
            else:
                output += tab + cmd.toGCode() + "\n"

if output:
    save2file(output)
else:
    print("Nothing to save")
