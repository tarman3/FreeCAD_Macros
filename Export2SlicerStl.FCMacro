# -*- coding: utf-8 -*-
# Opens current visible objects in Slic3r. One can use different slicing software

__Title__ = '3D Print / Slice'
__Author__ = 'Damian Łoziński'
__Version__ = '0.4.1'
__Date__ = '2024-08-28'
__Comment__ = 'Export selected objects to amf/stl files and open them in slicing program'
__Web__ = 'https://github.com/dlozinski/FreeCAD-macros/blob/doc/ImportExport/ExportToSlicer.md'
__Wiki__ = ''
__Icon__ = 'Export2Slicer.png'
__Help__ = 'You may need to change slicer path. To do so open Tools > Edit parameters > BaseApp/Preferences/Macros/Export2Slicer'
__Status__ = 'Stable'
__Requires__ = 'freecad 0.17+'
__Communication__ = 'lozinski dot d at gmail dot com'
__Files__ = 'Export2Slicer.png'

import os
import re
from subprocess import Popen
import shlex

import FreeCAD as app
import FreeCADGui as gui
import Mesh
import MeshPart


MACRO_PARAMS = app.ParamGet('User parameter:BaseApp/Preferences/Macros/Export2Slicer')
DEFAULT_SLICER_CMD = '"prusa-slicer" --single-instance "{file}"'
DEFAULT_OUTPUT_FORMAT = 'amf'
DEFAULT_ANGULAR_DEFLECTION = 0.07


def get_string_param(name, default):
    value = MACRO_PARAMS.GetString(name)
    if not value:
        MACRO_PARAMS.SetString(name, default)
        value = default
    return value


def get_float_param(name, default):
    value = MACRO_PARAMS.GetFloat(name)
    if not value:
        MACRO_PARAMS.SetFloat(name, default)
        value = default
    return value


slicer_cmd = get_string_param('SlicerCommand', DEFAULT_SLICER_CMD)
output_format = get_string_param('OutputFormat', DEFAULT_OUTPUT_FORMAT)
angular_deflection = get_float_param('AngularDeflection', DEFAULT_ANGULAR_DEFLECTION)


def escape(text):
    return re.sub(r'\W', '_', text)


def get_mesh_filename(doc_filename, mesh_names):
    """Returns valid filename for temporary mesh file."""
    if doc_filename:
        dirname = os.path.dirname(doc_filename)
        filename = (
            os.path.basename(doc_filename).partition('.')[0]
            + '-'
            + escape('_'.join(mesh_names))
            + '.'
            + output_format)
        file_path = os.path.join(dirname, filename)
    else:
        file_path = 'meshes-export.' + output_format
    return file_path


def main():
    doc = app.activeDocument()
    if not doc:
        raise RuntimeError('Export2Slicer: No active document')

    selection = gui.Selection.getSelectionEx()
    objects_to_export = [x.Object for x in selection] or [doc.ActiveObject]
    try:
        # Create temporary doc to store meshes so that we don't affect current doc history
        tmp_doc = app.newDocument('meshes_to_export', temp=True)
        meshes = []
        mesh_names = []
        for o in objects_to_export:
            if o.TypeId == 'Mesh::Feature':
                meshes.append(o)
            else:
                mesh = tmp_doc.addObject('Mesh::Feature', f'{doc.Label}_{o.Label}')
                mesh.Mesh = MeshPart.meshFromShape(o.Shape, LinearDeflection=0.1, AngularDeflection=angular_deflection, Relative=False)
                meshes.append(mesh)
                mesh_names.append(o.Label)
        if meshes:
            mesh_path = get_mesh_filename(doc.FileName, mesh_names)
            Mesh.export(meshes, mesh_path)
        else:
            raise RuntimeError('Export2Slicer: No objects to export')
    finally:
        app.closeDocument('meshes_to_export')
        for x in selection:
            gui.Selection.addSelection(doc.Name, x.ObjectName)

    # Launch Slicer with meshes
    Popen(shlex.split(slicer_cmd.format(file=mesh_path)))
    app.Console.PrintMessage(f'Export2Slicer: Objects exported into: {mesh_path}\n')


try:
    main()
except Exception as e:
    app.Console.PrintError('Export2Slicer: ERROR: {}\n'.format(e))
