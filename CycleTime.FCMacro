# Recompute CycleTime for selected Path object

import Path

import math
import time


def getCycleTimeEstimate(obj):
    tc = obj.ToolController
    
    if tc is None or tc.ToolNumber == 0:
        Path.Log.error(translate("CAM", "No Tool Controller selected."))
        return translate("CAM", "Tool Error")
    
    hFeedrate = tc.HorizFeed.Value
    vFeedrate = tc.VertFeed.Value
    hRapidrate = tc.HorizRapid.Value
    vRapidrate = tc.VertRapid.Value
    
    if (hFeedrate == 0 or vFeedrate == 0) and not Path.Preferences.suppressAllSpeedsWarning():
        Path.Log.warning(
            translate(
                "CAM",
                "Tool Controller feedrates required to calculate the cycle time.",
            )
        )
        return translate("CAM", "Feedrate Error")
    
    if (
        hRapidrate == 0 or vRapidrate == 0
    ) and not Path.Preferences.suppressRapidSpeedsWarning():
        Path.Log.warning(
            translate(
                "CAM",
                "Add Tool Controller Rapid Speeds on the SetupSheet for more accurate cycle times.",
            )
        )
    
    # Get the cycle time in seconds
    seconds = obj.Path.getCycleTime(hFeedrate, vFeedrate, hRapidrate, vRapidrate)
    
    if not seconds or math.isnan(seconds):
        return translate("CAM", "Cycletime Error")
    
    # Convert the cycle time to a HH:MM:SS format
    cycleTime = time.strftime("%H:%M:%S", time.gmtime(seconds))
    
    return cycleTime
    
selection = FreeCADGui.Selection.getSelection()
for obj in selection:
    if hasattr(obj, 'CycleTime'):
        obj.CycleTime = getCycleTimeEstimate(obj)
