import random

def main(obj):
    global outMessage
    vobj = obj.ViewObject
    if not hasattr(vobj, 'Selectable'): return None
    
    vobj.Selectable = False
    Gui.Selection.addSelection(doc.Name, obj.Name)

    if int(FreeCAD.Version()[0]) == 1 and int(FreeCAD.Version()[1]) > 0:
        transparency = 100 - vobj.Transparency*100
    else:
        transparency = float(vobj.Transparency/100)

    randColor = colMap[random.randint(0, len(colMap))-1]
    color = (
             randColor[0],
             randColor[1],
             randColor[2],
             # random.uniform(0,1),
             # random.uniform(0,1),
             # random.uniform(0,1),
             transparency/100
            )

    shapeType = obj.Shape.ShapeType if hasattr(obj, 'Shape') else None
    if shapeType:
        sobj = obj.Shape
        if (sobj.ShapeType in ('Wire', 'Edge')) \
        or ( (len(sobj.Edges)>0) and (len(sobj.Faces)==0) and (len(sobj.Vertexes)==0) ):
            vobj.LineColor = color

        elif (len(sobj.Vertexes)>0) and (len(sobj.Faces)==0) and (len(sobj.Edges)==0):
            vobj.PointColor = color

        else:
            sapp1 = vobj.ShapeAppearance[0]
            sapp1.DiffuseColor = color
            vobj.ShapeAppearance = (sapp1, )

    elif 'Mesh' in obj.TypeId:
        sapp1 = vobj.ShapeAppearance[0]
        sapp1.DiffuseColor = color
        vobj.ShapeAppearance = (sapp1, )

    outMessage = f'{outMessage}\n\
Label:     {obj.Label}\n\
TypeId:    {obj.TypeId}\n\
ShapeType: {shapeType}\n\
New Color: {color}\n'

    vobj.Selectable = True
        
        

colMap = (
    (0.000,0.187,0.963),(0.000,0.202,0.949),(0.000,0.217,0.935),(0.000,0.231,0.921),
    (0.011,0.244,0.908),(0.036,0.257,0.894),(0.056,0.269,0.880),(0.069,0.281,0.867),
    (0.079,0.292,0.853),(0.087,0.302,0.840),(0.092,0.313,0.826),(0.096,0.323,0.813),
    (0.098,0.333,0.799),(0.100,0.342,0.786),(0.100,0.352,0.772),(0.099,0.361,0.759),
    (0.098,0.370,0.745),(0.097,0.378,0.732),(0.095,0.386,0.719),(0.093,0.395,0.706),
    (0.092,0.402,0.693),(0.092,0.410,0.680),(0.092,0.417,0.667),(0.093,0.425,0.654),
    (0.095,0.432,0.641),(0.099,0.438,0.629),(0.104,0.445,0.616),(0.110,0.451,0.604),
    (0.117,0.457,0.592),(0.125,0.463,0.580),(0.134,0.469,0.568),(0.142,0.474,0.556),
    (0.151,0.480,0.544),(0.160,0.485,0.532),(0.169,0.491,0.520),(0.177,0.496,0.509),
    (0.185,0.501,0.497),(0.193,0.506,0.485),(0.200,0.511,0.473),(0.206,0.516,0.462),
    (0.213,0.522,0.450),(0.218,0.527,0.438),(0.223,0.532,0.426),(0.228,0.537,0.414),
    (0.232,0.542,0.402),(0.236,0.547,0.390),(0.239,0.552,0.378),(0.242,0.557,0.365),
    (0.245,0.562,0.353),(0.247,0.567,0.340),(0.249,0.573,0.327),(0.250,0.578,0.314),
    (0.252,0.583,0.301),(0.253,0.588,0.288),(0.254,0.593,0.275),(0.255,0.598,0.262),
    (0.256,0.603,0.248),(0.257,0.608,0.235),(0.258,0.613,0.221),(0.260,0.618,0.208),
    (0.263,0.623,0.195),(0.266,0.627,0.182),(0.270,0.632,0.169),(0.274,0.636,0.156),
    (0.280,0.641,0.144),(0.286,0.645,0.133),(0.293,0.649,0.122),(0.302,0.653,0.112),
    (0.311,0.657,0.102),(0.320,0.660,0.094),(0.331,0.664,0.086),(0.341,0.667,0.080),
    (0.353,0.671,0.075),(0.364,0.674,0.070),(0.376,0.677,0.067),(0.388,0.680,0.065),
    (0.400,0.683,0.064),(0.412,0.686,0.064),(0.425,0.689,0.064),(0.437,0.692,0.064),
    (0.449,0.695,0.065),(0.461,0.698,0.067),(0.473,0.701,0.068),(0.485,0.703,0.070),
    (0.496,0.706,0.071),(0.508,0.709,0.073),(0.520,0.712,0.075),(0.531,0.715,0.077),
    (0.542,0.717,0.078),(0.554,0.720,0.080),(0.565,0.723,0.082),(0.576,0.725,0.084),
    (0.587,0.728,0.086),(0.598,0.731,0.087),(0.609,0.733,0.089),(0.620,0.736,0.091),
    (0.631,0.739,0.093),(0.642,0.741,0.095),(0.653,0.744,0.096),(0.664,0.746,0.098),
    (0.674,0.749,0.100),(0.685,0.751,0.102),(0.696,0.754,0.103),(0.707,0.757,0.105),
    (0.717,0.759,0.107),(0.728,0.762,0.109),(0.738,0.764,0.111),(0.749,0.766,0.112),
    (0.759,0.769,0.114),(0.770,0.771,0.116),(0.780,0.774,0.118),(0.791,0.776,0.120),
    (0.801,0.778,0.121),(0.812,0.781,0.123),(0.822,0.783,0.125),(0.832,0.785,0.127),
    (0.843,0.787,0.128),(0.853,0.789,0.130),(0.863,0.791,0.132),(0.873,0.793,0.133),
    (0.882,0.794,0.135),(0.892,0.795,0.136),(0.901,0.796,0.137),(0.910,0.797,0.139),
    (0.918,0.797,0.140),(0.926,0.797,0.141),(0.933,0.796,0.142),(0.940,0.795,0.142),
    (0.946,0.793,0.143),(0.952,0.791,0.143),(0.957,0.789,0.143),(0.962,0.786,0.143),
    (0.966,0.782,0.143),(0.969,0.779,0.142),(0.972,0.774,0.142),(0.974,0.770,0.141),
    (0.976,0.765,0.140),(0.977,0.760,0.139),(0.978,0.754,0.138),(0.979,0.749,0.137),
    (0.979,0.743,0.136),(0.980,0.737,0.135),(0.980,0.732,0.133),(0.980,0.726,0.132),
    (0.979,0.720,0.131),(0.979,0.714,0.130),(0.979,0.707,0.128),(0.979,0.701,0.127),
    (0.978,0.695,0.126),(0.978,0.689,0.124),(0.977,0.683,0.123),(0.977,0.677,0.122),
    (0.976,0.670,0.121),(0.976,0.664,0.119),(0.975,0.658,0.118),(0.975,0.652,0.117),
    (0.974,0.645,0.116),(0.974,0.639,0.114),(0.973,0.633,0.113),(0.973,0.627,0.112),
    (0.972,0.620,0.111),(0.971,0.614,0.110),(0.971,0.608,0.108),(0.970,0.601,0.107),
    (0.969,0.595,0.106),(0.969,0.588,0.105),(0.968,0.582,0.104),(0.967,0.575,0.103),
    (0.966,0.569,0.102),(0.966,0.563,0.100),(0.965,0.556,0.099),(0.964,0.549,0.098),
    (0.963,0.543,0.097),(0.962,0.536,0.096),(0.961,0.530,0.095),(0.961,0.523,0.094),
    (0.960,0.516,0.093),(0.959,0.510,0.092),(0.958,0.503,0.091),(0.957,0.496,0.090),
    (0.956,0.489,0.089),(0.955,0.482,0.088),(0.954,0.476,0.087),(0.953,0.469,0.086),
    (0.952,0.462,0.085),(0.951,0.455,0.084),(0.950,0.448,0.083),(0.949,0.440,0.083),
    (0.948,0.433,0.082),(0.947,0.426,0.082),(0.946,0.419,0.082),(0.945,0.412,0.082),
    (0.944,0.405,0.083),(0.943,0.398,0.084),(0.942,0.391,0.086),(0.941,0.384,0.088),
    (0.941,0.378,0.091),(0.940,0.371,0.095),(0.940,0.365,0.100),(0.940,0.360,0.106),
    (0.940,0.355,0.113),(0.940,0.350,0.121),(0.941,0.346,0.130),(0.942,0.343,0.139),
    (0.943,0.340,0.150),(0.944,0.338,0.161),(0.946,0.337,0.173),(0.948,0.337,0.186),
    (0.950,0.338,0.199),(0.952,0.339,0.213),(0.954,0.341,0.227),(0.957,0.343,0.242),
    (0.959,0.346,0.257),(0.962,0.350,0.272),(0.965,0.354,0.288),(0.967,0.358,0.304),
    (0.970,0.362,0.320),(0.973,0.367,0.336),(0.975,0.372,0.352),(0.978,0.377,0.368),
    (0.980,0.382,0.385),(0.983,0.387,0.401),(0.985,0.392,0.418),(0.987,0.397,0.434),
    (0.990,0.403,0.451),(0.992,0.408,0.467),(0.993,0.413,0.484),(0.995,0.418,0.500),
    (0.997,0.424,0.517),(0.999,0.429,0.533),(1.000,0.434,0.550),(1.000,0.440,0.567),
    (1.000,0.445,0.583),(1.000,0.451,0.600),(1.000,0.456,0.617),(1.000,0.461,0.634),
    (1.000,0.467,0.651),(1.000,0.472,0.668),(1.000,0.478,0.685),(1.000,0.483,0.702),
    (1.000,0.488,0.719),(1.000,0.494,0.736),(1.000,0.499,0.753),(1.000,0.505,0.770),
    (1.000,0.510,0.787),(1.000,0.516,0.805),(1.000,0.521,0.822),(1.000,0.527,0.840),
    (1.000,0.532,0.857),(1.000,0.538,0.874),(1.000,0.544,0.892),(1.000,0.549,0.910),
    (0.998,0.555,0.927),(0.997,0.560,0.945),(0.995,0.566,0.963),(0.992,0.572,0.980)
)



objList = FreeCADGui.Selection.getSelection()
#obj = objList[0] # for debuging

outMessage = f'<<< Macros RandomColor >>>'

if not objList:
    outMessage = f'{outMessage}\nNothing selected'

else:
    Gui.Selection.clearSelection()
    
    doc = App.ActiveDocument
    
    for obj in objList:
        if obj.TypeId == 'App::DocumentObjectGroup':
            for groupObj in obj.Group:
                main(groupObj)
        else:
            main(obj)

print(outMessage)
