__title__ = "Select all faces of an object"
__doc__ = ""
__author__ = "OpenSource CNC"
__url__ = "https://www.patreon.com/collection/657672"


from FreeCADGui import Selection

selections = Selection.getSelection()
Gui.Selection.clearSelection()

for sel in selections:
    obj=sel.Shape
    hits = []
    index = 0

    for face in obj.Faces:
        hits.append(f"Face{index + 1}")
        index += 1

    print(f"Selected {len(hits)} faces from object {sel.Label}")
    print(hits)
    Gui.Selection.addSelection(sel, hits)
