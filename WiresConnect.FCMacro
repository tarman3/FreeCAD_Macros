__title__ = "Wires connect"
__doc__ = "Connect multiple wires to one wire"
__url__ = ""

import FreeCADGui
import Part

threshold = 10

selection = FreeCADGui.Selection.getSelection()

wires = selection[0].Shape.Wires
wires.sort(key=lambda wire: wire.BoundBox.Center.z, reverse=True)

end = -1
joints = []
for i in range(len(wires) - 1):

    start = 0 if end == -1 else -1

    p = wires[i].OrderedVertexes[end].Point
    p1 = wires[i+1].OrderedVertexes[start].Point
    p2 = wires[i+1].OrderedVertexes[end].Point

    if p.distanceToPoint(p1) < threshold:
        end = -1 if start == 0 else 0
        line = Part.LineSegment(p, p1)

    elif p.distanceToPoint(p2) < threshold:
        end = -1 if end == 0 else 0
        line = Part.LineSegment(p, p2)

    joints.append(Part.Wire(Part.Shape(line)))


wires.extend(joints)
edges = [edge for wire in wires for edge in wire.Edges]

for sortedEdges in Part.sortEdges(edges):
    wire = Part.Wire(sortedEdges)
    Part.show(wire)
