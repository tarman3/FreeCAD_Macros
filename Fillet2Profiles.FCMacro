__title__ = "Create gcode for processing fillet by BallEnd or Endmill"
__doc__ = ""
__url__ = "https://forum.freecad.org/viewtopic.php?t=94642"


print()
print('--- Macro to create gcode for processing fillet by BallEnd or Endmill ---')

"""
1. Create Job
2. Add BallEnd or Endmill tool
3. Create Profile for top contour
   Check Final Depth must be the same like Height of the top profile
   Side = Outside (for fillet on outer side)
4. Check parameters in macro
   step = Max vertical or horizontal movement
   filletRadius = Radius of the fillet
5. Select Profile operation and edge or shape to determine radius of fillet
6. Execute macro
   Check Report view if needed
"""

step = 0.2       # Max vertical or horizontal movement
inc = step/10    # Step for calculation
filletRadius = 5

import PathScripts.PathUtils as PathUtils

sel = FreeCADGui.Selection.getSelectionEx()
if not sel:
    print(f'  Please select base profile in top of fillet')

else:
    origProfile = [s.Object for s in sel if "Profile" in s.Object.Name][0]

    for s in sel:
        if s.Object.isDerivedFrom("Part::Feature"):
            obj = s.Object
            subName = s.SubElementNames[0]
            if "Edge" in subName:
                edge = obj.Shape.getElement(subName)
                if hasattr(edge.Curve, "Radius"):
                    filletRadius = edge.Curve.Radius
                    break
            elif "Face" in subName:
                face = obj.Shape.getElement(subName)
                if hasattr(face.Surface, "Radius"):
                    filletRadius = face.Surface.Radius
                    break
                if hasattr(face.Surface, "MinorRadius"):
                    filletRadius = face.Surface.MinorRadius
                    break
    else:
        print(f"  Can not determine radius from selected shape. Used default value {filletRadius}")

    # subBase = sel[0].SubElementNames[0]

    # Create copy of Profile
    baseProfile = FreeCAD.ActiveDocument.copyObject(origProfile)
    job = PathUtils.findParentJob(origProfile)
    job.Proxy.addOperation(baseProfile)

    baseProfile.setExpression("FinalDepth", None)
    baseProfile.setExpression("StartDepth", None)
    baseProfile.setExpression("StepDown", None)

    tool = baseProfile.ToolController.Tool
    toolDiam = tool.Diameter.Value
    toolShapeType = tool.ShapeType

    if "ballend" in toolShapeType.casefold():
        baseProfile.UseComp = False
    else:
        baseProfile.UseComp = True

    baseProfile.StartDepth = baseProfile.FinalDepth.Value
    baseProfile.StepDown = filletRadius + toolDiam + 0.1
    baseProfile.OffsetExtra = 0

    startDepth = baseProfile.StartDepth.Value
    if "ballend" in toolShapeType.casefold():
        finalDepth = startDepth - toolDiam/2 - filletRadius
        effectiveRadius = filletRadius + toolDiam/2
    else:
        finalDepth = startDepth - filletRadius
        effectiveRadius = filletRadius

    gcode = []
    currentDepth = startDepth

    for i in range (1, 100, 1):
        effectiveHeight = effectiveRadius - (startDepth-currentDepth)
        offsetExtraPrev = (effectiveRadius**2 - effectiveHeight**2)**0.5
        currentDepthPrev = currentDepth
        for j in range(1, 100, 1):
            currentDepth -= inc
            effectiveHeight = effectiveRadius - (startDepth-currentDepth)
            offsetExtra = (effectiveRadius**2 - effectiveHeight**2)**0.5

            if (
               (offsetExtra - offsetExtraPrev) >= step
               or (currentDepthPrev - currentDepth) >= step
               or currentDepth <= finalDepth
            ):
                # Get next optimal depth
                break
        else:
            print(f"  Macro overlimit B")

        if currentDepth <= finalDepth + 0.001: break


        # print(f'  depth={currentDepth:.2f} OffsetExtra={offsetExtra:.2f}')

        # Set currentDepth and offsetExtra to Profile
        baseProfile.FinalDepth = currentDepth
        baseProfile.OffsetExtra = offsetExtra
        baseProfile.recompute()
        gcodeCurrent = [c.toGCode() for c in baseProfile.Path.Commands]

        # Get gcode from profile path
        gcode += gcodeCurrent

    else:
        print(f'  Macro overlimit A')

    # Delete copy of Profile
    FreeCAD.ActiveDocument.removeObject(baseProfile.Name)

    print(f"  filletRadius={filletRadius}  startDepth={startDepth}  finalDepth={finalDepth}")
    print(f"  toolShapeType={toolShapeType}  toolDiam={toolDiam}")

    res = Path.Op.Gui.Custom.Command.res
    filletGcode = Path.Op.Custom.Create("filletGcode")
    filletGcode.ViewObject.Proxy = Path.Op.Gui.Custom.PathOpGui.ViewProvider(filletGcode.ViewObject, res)
    filletGcode.Gcode = gcode
    filletGcode.ViewObject.Visibility = True
    filletGcode.ViewObject.Proxy.deleteOnReject = False
    filletGcode.recompute()
