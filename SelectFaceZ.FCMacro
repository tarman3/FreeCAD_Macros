toleranceZ = 0.01

def getFacesZ(body, targetZ, toleranceZ):
    facesZ = []
    for i, face in enumerate(body.Shape.Faces):
        center = face.CenterOfMass
        if abs(center.z - targetZ) <= toleranceZ:
            facesZ.append((i+1, face))  # (index, face)
    return facesZ


selExList = FreeCADGui.Selection.getSelectionEx('', 0)

print()
print(f'<<< Macro selecting faces with equal Z >>>')
if not selExList:
    print(f'    >>> Nothing selected <<<')

else:
    counter = 0
    for selEx in selExList:
        objSel = selEx.Object
        sub = selEx.SubElementNames[0]
        body = objSel.getSubObject(sub, 1)
        for face in selEx.SubObjects:
            if face.Faces:
                faceDepth = face.CenterOfMass.z
                faces = getFacesZ(body, faceDepth, toleranceZ)
                print(f'    Found {len(faces)} face(s) near Z = {faceDepth:.2f} \u00B1 {toleranceZ}')

                for i, face in faces:
                    counter += 1
                    Gui.Selection.addSelection(body, str('Face'+str(i)))
if counter == 0:
    print(f'    No selected faces')
